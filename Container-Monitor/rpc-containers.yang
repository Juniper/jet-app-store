module rpc-docker-containers {
  namespace "http://yang.juniper.net/examples/rpc-cli";
  prefix rpc-cli;

  import junos-extension {
    prefix junos;
  }

  import junos-extension-odl {
    prefix junos-odl;
  }

  organization
    "Juniper Networks, Inc.";

  description
    "Docker Container Monitoring Tool";

  rpc get-docker-containers {
     description "Show all running containers";

     junos:command "show docker containers";
     junos:action-execute {
       junos:script "cmonitor.py";
     }


    output {
      container docker-container-info {
        container container-info {
          leaf hostname {
            type string;
            description "Hostname of node running the container";
          }
          leaf service {
            type string;
            description "Name of service";
          }
          leaf containerID {
            type string;
            description "First 16 chars of container ID";
          }
          leaf port {
            type string;
            description "Exposed ports from inside container to host";
          }
          leaf socketRemote {
            type string;
            description "Node port that connects to device";
          }
          leaf socketHost {
            type string;
            description "Device port that connects to node";
          }
          container container-info-format {
            junos-odl:cli-format;
            junos-odl:header "NODE\t\t   SERVICE NAME\t  CONTAINER ID\t     PORTS\t    SWITCH PHYSICAL PORT  SERVER PHYSICAL PORT\n";
            junos-odl:picture "@<<<<<<<<<<<<<<<<< @||||||||||||| @||||||||||||||||| @||||||||||||| @|||||||||||||  @>>>>>>>>>";
            junos-odl:line {
              junos-odl:field "hostname";
              junos-odl:field "service";
              junos-odl:field "containerID";
              junos-odl:field "port";
              junos-odl:field "socketRemote";
              junos-odl:field "socketHost";
            }
        }
        
    }
    }
  }
  }
}
